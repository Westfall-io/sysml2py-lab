package 'Constraints Example-1' {
    	public import ISQ::*;
    	public import SI::*;
    	public import NumericalFunctions::*;
    	
    	part def Engine;
    	part def Transmission;
    	
    	constraint def MassConstraint {
    		in partMasses : MassValue[0..*];
    		in massLimit : MassValue;
    			
    		sum(partMasses) <= massLimit
    	}
    	
    	part def Vehicle {
    		constraint massConstraint : MassConstraint {
    			in partMasses = (chassisMass, engine.mass, transmission.mass);
    			in massLimit = 2500[kg];
    		}
    		
    		attribute chassisMass : MassValue;
    		
    		part engine : Engine {
    			attribute mass : MassValue;
    		}
    		
    		part transmission : Engine {
    			attribute mass : MassValue;
    		}
    	}
    }
