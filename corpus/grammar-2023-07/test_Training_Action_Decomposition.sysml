package 'Action Decomposition' {
    	part def Scene;
    	part def Image;
    	part def Picture;
    	
    	action def Focus { in scene : Scene; out image : Image; }
    	action def Shoot { in image: Image; out picture : Picture; }	
    	action def TakePicture { in scene : Scene; out picture : Picture; }
    		
    	action takePicture : TakePicture {
    		in item scene;
    		out item picture;
    		
    		action focus : Focus {
    			in item scene = takePicture::scene; 
    			out item image;
    		}
    		
    		flow focus.image to shoot.image;

    		action shoot : Shoot {
    			in item; 
    			out item picture = takePicture::picture;
    		}
    	}
    	
    }
