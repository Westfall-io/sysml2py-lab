package 'Flow Connection Definition Example' {
    	public import 'Port Example'::*;

    	part def Vehicle;

    	flow def FuelFlow {
    		ref :>> payload : Fuel;
    		end port supplierPort : FuelOutPort;
    		end port consumerPort : FuelInPort;
    	}

    	part vehicle : Vehicle {
    		part tankAssy : FuelTankAssembly;
    		part eng : Engine;

    		flow : FuelFlow
    		  from tankAssy.fuelTankPort.fuelSupply
    			to eng.engineFuelPort.fuelSupply;

    	}
    }
