package 'Items Example' {
    	public import ScalarValues::*;

    	item def Fuel;
    	item def Person;

    	part def Vehicle {
    		attribute mass : Real;

    		ref item driver : Person;

    		part fuelTank {
    			item fuel: Fuel;
    		}
    	}

    }
