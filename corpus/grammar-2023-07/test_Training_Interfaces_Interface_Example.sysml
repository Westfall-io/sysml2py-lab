package 'Interface Example' {
    	public import 'Port Example'::*;

    	part def Vehicle;

    	interface def FuelInterface {
    		end supplierPort : FuelOutPort;
    		end consumerPort : FuelInPort;
    	}

    	part vehicle : Vehicle {
    		part tankAssy : FuelTankAssembly;
    		part eng : Engine;

    		interface : FuelInterface connect
    			supplierPort ::> tankAssy.fuelTankPort to
    			consumerPort ::> eng.engineFuelPort;
    	}
    }
