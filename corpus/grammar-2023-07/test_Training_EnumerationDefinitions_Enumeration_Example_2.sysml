package 'Enumeration Definitions-2' {
    	public import ScalarValues::*;
    	public import 'Enumeration Definitions-1'::*;

    	attribute def ClassificationLevel {
    		attribute code : String;
    		attribute color : TrafficLightColor;
    	}

    	enum def ClassificationKind specializes ClassificationLevel {
    		unclassified {
    			:>> code = "uncl";
    			:>> color = TrafficLightColor::green;
    		}
    		confidential {
    			:>> code = "conf";
    			:>> color = TrafficLightColor::yellow;
    		}
    		secret {
    			:>> code = "secr";
    			:>> color = TrafficLightColor::red;
    		}
    	}

    	enum def GradePoints :> Real {
    		A = 4.0;
    		B = 3.0;
    		C = 2.0;
    		D = 1.0;
    		F = 0.0;
    	}
    }
