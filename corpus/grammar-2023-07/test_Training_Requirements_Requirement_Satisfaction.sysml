package 'Requirement Satisfaction' {
    	public import 'Requirement Groups'::*;
    	
    	action 'provide power' {
    		action 'generate torque';
    	}
    	
    	part vehicle_c1 : Vehicle {
    		perform 'provide power';
    			
    		part engine_v1: Engine {
    			port :>> clutchPort;
    			perform 'provide power'.'generate torque' :>> generateTorque;
    		}	
    	}
    	
    	part 'Vehicle c1 Design Context' {
    		
    		ref vehicle_design :> vehicle_c1;
    	
    		satisfy vehicleSpecification by vehicle_design;
    		satisfy engineSpecification by vehicle_design.engine_v1;
    	
    	}
    	
    }
