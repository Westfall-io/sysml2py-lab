package 'Calculation Definitions' {
    	public import ScalarValues::Real;
    	public import ISQ::*;
    	
    	calc def Power { in whlpwr : PowerValue; in Cd : Real; in Cf : Real; in tm : MassValue; in v : SpeedValue;
    		attribute drag = Cd * v;
    		attribute friction = Cf * tm * v;
    		
    		return : PowerValue = whlpwr - drag - friction;
    	}
    	
    	calc def Acceleration { in tp: PowerValue; in tm : MassValue; in v : SpeedValue;
    		return : AccelerationValue = tp / (tm * v);
    	}
    	
    	calc def Velocity { in dt : TimeValue; in v0 : SpeedValue; in a : AccelerationValue;
    		return : SpeedValue = v0 + a * dt;
     	}
     	
    	calc def Position { in dt : TimeValue; in x0 : LengthValue; in v : SpeedValue;
    		return : LengthValue = x0 + v * dt;
    	}
    }
