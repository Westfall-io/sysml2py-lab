package 'Trade Study Analysis Example' {
    	public import ScalarValues::Real;
    	public import TradeStudies::*;
    	
    	part def Engine;
    	part engine4cyl : Engine;
    	part engine6cyl : Engine;
    	
    	calc def PowerRollup { in engine : Engine; return : ISQ::PowerValue; }
    	calc def MassRollup { in engine : Engine; return : ISQ::MassValue; }
    	calc def EfficiencyRollup { in engine : Engine; return : Real; }
    	calc def CostRollup { in engine : Engine; return : Real; }
    	
    	calc def EngineEvaluation { 
    		in power : ISQ::PowerValue;
    		in mass : ISQ::MassValue;
    		in efficiency : Real;
    		in cost : Real;
    		return evaluation : Real;
    	}
    		
    	analysis engineTradeStudy : TradeStudy {
    		subject : Engine = (engine4cyl, engine6cyl);
    		objective : MaximizeObjective;

    		calc :>> evaluationFunction {
    			in part anEngine :>> alternative : Engine;
    			
    			calc powerRollup: PowerRollup { in engine = anEngine; return power; }
    			calc massRollup: MassRollup { in engine = anEngine; return mass; }
    			calc efficiencyRollup: EfficiencyRollup { in engine = anEngine; return efficiency; }
    			calc costRollup: CostRollup { in engine = anEngine; return cost; }
    			
    			return :>> result : Real = EngineEvaluation(
    				powerRollup.power, massRollup.mass, efficiencyRollup.efficiency, costRollup.cost
    			);
    		}
    		
    		return part :>> selectedAlternative : Engine;
    	}
    	
    }
